Private Sub Main()
	Dim oInvApp As Inventor.Application = ThisApplication
	Dim oDoc As Document = oInvApp.ActiveDocument
	Dim oTM As TransactionManager = oInvApp.TransactionManager
	If TypeOf oDoc Is AssemblyDocument Then
		Dim oAssDoc As AssemblyDocument = oDoc
		Dim oSelSet As SelectSet = oAssDoc.SelectSet
		If oSelSet.Count < 1 Then
			MessageBox.Show("It is necessary to select at least one component!", "Error!", _
							MessageBoxButtons.OK, MessageBoxIcon.Error)
			Exit Sub
		End If
		Dim sListOccs As New List(Of ComponentOccurrence)
		For i As Integer = 1 To oSelSet.Count
			If TypeOf oSelSet.Item(i) Is ComponentOccurrence Then
				sListOccs.Add(oSelSet.Item(i))
			End If
		Next i
		Dim newTM As Transaction = oTM.StartTransaction(oAssDoc, "Constraints_XYZ")
		For iOcc As Integer = 0 To sListOccs.Count - 1
			Call CreatFlushConstraints(oAssDoc.ComponentDefinition, sListOccs(iOcc))
		Next
		newTM.End
	Else
		MessageBox.Show("This rule is intended for work with assemblies!", "Error!", _
						MessageBoxButtons.OK, MessageBoxIcon.Error)
	End If 
End Sub

Private Function CreatFlushConstraints(ByVal oAssDef As AssemblyComponentDefinition,
										ByVal oOcc As ComponentOccurrence)
	Dim oAsmPlane As WorkPlane
	Dim oPartPlane As WorkPlane
	Dim oPartPlaneProxy As WorkPlaneProxy
	For i As Integer = 1 To 3
		oAsmPlane = oAssDef.WorkPlanes(i)
		oPartPlane = oOcc.Definition.WorkPlanes(i)
		Call oOcc.CreateGeometryProxy(oPartPlane, oPartPlaneProxy)
		Call oAssDef.Constraints.AddFlushConstraint(oPartPlaneProxy, oAsmPlane, 0)
	Next i
End Function
