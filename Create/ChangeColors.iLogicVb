' <FireOthersImmediately>False</FireOthersImmediately>
Sub main()
	Dim oDoc As Document = ThisDoc.Document
	Dim colorList As New ArrayList
	Dim oAssetlib As AssetLibrary
	For Each oAssetlib In ThisApplication.AssetLibraries
	    Dim oAsset As Asset
	    For Each oAsset In oAssetlib.AppearanceAssets
	         colorList.Add(oAsset.DisplayName)
	    Next
	Next
	colorList.Sort
	Dim oFaces As Faces
	Dim oFace As Face
	Dim ActAppLib As AssetLibrary
	ActAppLib = ThisApplication.ActiveAppearanceLibrary
	oDoc.Update
	If TypeOf oDoc Is AssemblyDocument Then
		oFace = ThisApplication.CommandManager.Pick(SelectionFilterEnum.kAllPlanarEntities, "Оберіть грань з необхідним кольором")
		If IsNothing(oFace) Then Exit Sub
		Dim SelectColor As String = oFace.Appearance.DisplayName
		Dim NewColor As String
		NewColor = InputListBox("Оберіть бажаний колір.", colorList, colorList(colorList.IndexOf(SelectColor)),
					Title := "Новий колір:", ListName := "Існуючий колір: " & SelectColor)
		If IsNothing(NewColor) Then Exit Sub
		Call AllDoc(oDoc.AllReferencedDocuments, SelectColor, NewColor)
		oDoc.Update
	ElseIf TypeOf oDoc Is PartDocument Then
		Dim oDef As PartComponentDefinition = oDoc.ComponentDefinition
		If oDef.BOMStructure = BOMStructureEnum.kNormalBOMStructure Then
			oFaces = oDef.SurfaceBodies(1).Faces
			Dim KnotList As New List(Of String)
			Dim SelectColor As String
			Dim ListName As String
			For Each oFace In oFaces
				If KnotList.Count = 0 Then
					KnotList.Add(oFace.Appearance.DisplayName)
				Else
					If Not KnotList.Contains(oFace.Appearance.DisplayName) Then
						KnotList.Add(oFace.Appearance.DisplayName)
					End If
				End If
			Next
			If KnotList.Count > 1 Then
				SelectColor = InputListBox("Оберіть який колір ви хочете замінити.", KnotList, KnotList(0), Title := "Існуючі кольори:", ListName := oDoc.DisplayName)
				If IsNothing(SelectColor) Then Exit Sub
			ElseIf KnotList.Count = 1 Then
				SelectColor = KnotList(0)
			Else
				MessageBox.Show("Правило не знайшло кольорів на гранях.", "Помилка!")
				Exit Sub
			End If
			Dim NewColor As String
			NewColor = InputListBox("Оберіть бажаний колір.", colorList, colorList(colorList.IndexOf(SelectColor)),
						Title := "Новий колір:", ListName := oDoc.DisplayName)
			If IsNothing(NewColor) Then Exit Sub
			Call ChangeColorPart(oDoc, NewColor, SelectColor)
		Else
			MessageBox.Show("Неможливо виконати з придбаними деталями.", "Помилка!")
			Exit Sub
		End If
	Else
		MessageBox.Show("Неможливо виконати у Вашому документі. Працює з: AssemblyDocument, PartDocument.", "Помилка!")
		Exit Sub
	End If
End Sub

Public Sub AllDoc(oDocRef As DocumentsEnumerator, SelectColor As String, NewColor As String)
	Dim oProgressBar As Inventor.ProgressBar
    oMessage = "Updating... " 
	oProgressBar = ThisApplication.CreateProgressBar(False, oDocRef.Count, oMessage)
    oProgressBar.Message = ("Loading... ")
	For Each PartDoc As _Document In oDocRef
		Dim oPartDef As ComponentDefinition = PartDoc.ComponentDefinition
		If oPartDef.Type = kPartComponentDefinitionObject Or oPartDef.Type = kSheetMetalComponentDefinitionObject Then
			Dim oPartDoc As PartDocument = PartDoc
			If oPartDef.BOMStructure = BOMStructureEnum.kNormalBOMStructure Or
				oPartDef.BOMStructure = BOMStructureEnum.kPurchasedBOMStructure Then
				Dim strLocName, strLocType As String
				oPartDoc.GetLocationFoundIn(strLocName, strLocType)
				If Not strLocType = kLibraryLocation Then
					Call ChangeColorPart(oPartDoc, NewColor, SelectColor)
				End If
			End If
		End If
        oProgressBar.Message = ("Change colors in parts. Progress " & i & " of " & oDocRef.Count & ".")
        oProgressBar.UpdateProgress
		i = i+1
	Next
	oProgressBar.Close
End Sub

Public Sub ChangeColorPart(oDoc As PartDocument, NewColor As String, SelectColor As String)
	Dim oFaces As Faces = oDoc.ComponentDefinition.SurfaceBodies(1).Faces
	Dim oFace As Face
	Dim asset As Asset = Nothing
	Dim assetLib As AssetLibrary
	Try
		asset = oDoc.Assets.Item(NewColor)
	Catch
		If NewColor.Contains("RAL") Then
			assetLib = ThisApplication.AssetLibraries.Item("5F1643F1-74AC-4477-A0D1-3F4A78F70BE8")  '("КТВ_Текстури")
		Else
			assetLib = ThisApplication.AssetLibraries.Item("314DE259-5443-4621-BFBD-1730C6CC9AE9")  '("Autodesk Appearance Library")
		End If
		asset = assetLib.AppearanceAssets.Item(NewColor)
		asset = asset.CopyTo(oDoc)
	End Try
	Dim KnotList As New List(Of String)
	For Each oFace In oFaces
		If KnotList.Count = 0 Then
			KnotList.Add(oFace.Appearance.DisplayName)
		Else
			If Not KnotList.Contains(oFace.Appearance.DisplayName) Then
				KnotList.Add(oFace.Appearance.DisplayName)
			End If
		End If
	Next
	If KnotList.Count = 1 Then
		oDoc.ActiveAppearance = asset
		For Each obj In oDoc.ComponentDefinition.AppearanceOverridesObjects
			If TypeOf obj Is SurfaceBody Then
		        obj.AppearanceSourceType = _
				AppearanceSourceTypeEnum.kPartAppearance
		    ElseIf TypeOf obj Is PartFeature Then
		        obj.AppearanceSourceType = _
				AppearanceSourceTypeEnum.kBodyAppearance
'			ElseIf TypeOf obj Is Face Then
'		        obj.AppearanceSourceType = _
'				AppearanceSourceTypeEnum.kFeatureAppearance
		    End If
		Next
	Else
		For Each oFace In oFaces
			If oFace.Appearance.DisplayName = SelectColor Then
				oFace.Appearance = asset
			End If
		Next
	End If
End Sub
