Dim oDoc As PartDocument = ThisDoc.Document
If oDoc.FileSaveCounter = 0 Then Exit Sub
Dim oUOfM As UnitsOfMeasure = oDoc.UnitsOfMeasure
Dim oInvSummInfo As PropertySet = oDoc.PropertySets("Inventor Summary Information")
Dim oDocSummInfo As PropertySet = oDoc.PropertySets("Inventor Document Summary Information")
Dim oDesTrackProps As PropertySet = oDoc.PropertySets("Design Tracking Properties")
Dim oInvUserInfo As PropertySet = oDoc.PropertySets("Inventor User Defined Properties")
Dim oDocDef As PartComponentDefinition = oDoc.ComponentDefinition
Dim oUsParams As UserParameters = oDocDef.Parameters.UserParameters

Dim L_size As Double
Dim WebLink As String = oDesTrackProps("Catalog Web Link").Value
If WebLink = "ДСТУ 4747" Or WebLink = "ДСТУ 4738" Then
	L_size = oUOfM.ConvertUnits(oUsParams("G_L").Value, UnitsTypeEnum.kCentimeterLengthUnits, oUOfM.LengthUnits)
Else
	L_size = oUOfM.ConvertUnits(oUsParams("B_L").Value, UnitsTypeEnum.kCentimeterLengthUnits, oUOfM.LengthUnits)
End If
If L_size = 0 Then L_size = Measure.ExtentsHeight
Dim sName As String = System.IO.Path.GetFileNameWithoutExtension(oDoc.FullFileName)	
If oDesTrackProps("Part Number").Value <> sName.Substring(0, sName.IndexOf(" ")) Then
	oDesTrackProps("Part Number").Value = sName.Substring(0, sName.IndexOf(" "))
End If
If oInvSummInfo("Title").Value <> sName.Remove(0, sName.IndexOf(" ") + 1) Then
	oInvSummInfo("Title").Value = sName.Remove(0, sName.IndexOf(" ") + 1)
End If		
Dim NumberSize As String = oInvSummInfo("Subject").Value
Dim RevNumb As String = oInvSummInfo("Revision Number").Value
Dim oDocMat As MaterialAsset = oDoc.ActiveMaterial
Dim sMatName As String = oDocMat.DisplayName
Dim MatDensity As AssetValue = oDocMat.PhysicalPropertiesAsset.Item("structural_Density")
Dim oDensity As Double = MatDensity.Value
Dim oFeat As PartFeature = oDocDef.SurfaceBodies(1).CreatedByFeature

Dim Round As Inventor.Property
Try : Round = oInvUserInfo("Round_y") : Catch :	Round = oInvUserInfo.Add(1,"Round_y") :	End Try
Dim Round_y, inc As Double
Round_y = Round.Value
If Round_y <> 0 Then
	If Round_y > 0 And Round_y < 1 Then
		inc = Round_y
		Leng = Math.Round(Math.Round(L_size, 4) / inc) * inc
	ElseIf Round_y = 1 Then
		Leng = Math.Round(L_size)
	ElseIf Round_y > 1 And Round_y < 10 Then
		inc = Round_y / 10
		Leng = (Math.Round(Math.Round((L_size / 10), 4) / inc) * inc) * 10
	ElseIf Round_y >= 10 And Round_y < 100 Then
		inc = Round_y / 100
		Leng = (Ceil(Math.Round((L_size / 100), 4) / inc) * inc) * 100
	ElseIf Round_y >= 100 And Round_y < 1000 Then
		inc = Round_y / 1000
		Leng = (Ceil(Math.Round((L_size / 1000), 4) / inc) * inc) * 1000
	ElseIf Round_y >= 1000 Then
		inc = 0.1
		Leng = (Ceil(Math.Round((L_size / 10000), 4) / inc) * inc) * 10000
	End If
	
	If oDocSummInfo("Company").Value = "" Then
		If oInvSummInfo("Title").Value <> "" & RevNumb & " " & NumberSize & ", L=" & Leng & " мм" Then
			oInvSummInfo("Title").Value = "" & RevNumb & " " & NumberSize & ", L=" & Leng & " мм"
		End If
		If Round_y = 0 Then
			If oInvSummInfo("Title").Value <> sName.Remove(0, sName.IndexOf(" ") + 1) Then
				oInvSummInfo("Title").Value = sName.Remove(0, sName.IndexOf(" ") + 1)
			End If
		End If
	End If
	Try : oInvUserInfo("Main_size").Value = Leng / 1000 : Catch : oInvUserInfo.Add(Leng / 1000, "Main_size") : End Try
End If
Try : oInvUserInfo("Stren_steel").Value = oDocMat.PhysicalPropertiesAsset.DisplayName
Catch : oInvUserInfo.Add(oDocMat.PhysicalPropertiesAsset.DisplayName, "Stren_steel") : End Try 'Клас міцності
Try : oInvUserInfo("Stan_steel").Value = oDocMat("physmat_Comments").Value
Catch : oInvUserInfo.Add(oDocMat("physmat_Comments").Value, "Stan_steel") : End Try 'Стандарт матеріала
Try : oInvUserInfo("Area_Color").Value = Math.Round((L_size * oFeat.Profile.RegionProperties.Perimeter) / 100000, 3)
Catch : oInvUserInfo.Add(Math.Round((L_size * oFeat.Profile.RegionProperties.Perimeter) / 1000000, 3), "Area_Color") : End Try
