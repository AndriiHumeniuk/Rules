Dim oDoc As Document = ThisDoc.Document
Dim oComp As PartComponentDefinition = oDoc.ComponentDefinition
Dim oCustom As PropertySet = oDoc.PropertySets("Inventor User Defined Properties")
Dim oUParams As UserParameters = oComp.Parameters.UserParameters
Dim oUParam As UserParameter

Dim sList() As String = {"ГОСТ 13568-97", "ISO 606:2004" }
Try : oUParam = oUParams("Stand")
Catch : oUParam = oUParams.AddByExpression("Stand", sList(0), UnitsTypeEnum.kTextUnits)
End Try
For i As Integer = 0 To sList.Length - 1
	sList(i) = "" & sList(i) & ""
Next i

Dim oExpList As ExpressionList = oUParam.ExpressionList
Call oExpList.SetExpressionList(sList, false, 1)
If oExpList.AllowCustomValues Then oExpList.AllowCustomValues = False

Dim Стандарт As String
Стандарт = InputListBox("Виберіть стандарт ланцюга", oUParam.ExpressionList, "", "Список", "Номер редакции:")
If String.IsNullOrEmpty(Стандарт) Then Exit Sub

Try : oCustom("Standart").Value = Стандарт
Catch : oCustom.Add(Стандарт, "Standart", kTextUnits)
End Try

oDoc.Update()

iLogicVb.RunExternalRule("Chain iProperties")
