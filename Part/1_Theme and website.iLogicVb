Sub main
	oInvApp = ThisApplication
	oDoc = ThisDoc.Document
	Dim oDef As PartComponentDefinition = oDoc.ComponentDefinition
	If oDoc.FileSaveCounter = 0 Or oDoc.IsModifiable = False Or oDef.SurfaceBodies.Count <> 1 Then Exit Sub
	Dim oRevNumb As Inventor.Property = oDoc.PropertySets("Inventor Summary Information")("Revision Number")
	Dim Тема As String = oRevNumb.Value
	Dim oProject As PropertySet = oDoc.PropertySets("Design Tracking Properties")
	Dim oWebLink As Inventor.Property = oProject("Catalog Web Link")
	Dim Веб_сайт As String = oWebLink.Value
	Dim i As Integer = 0
	
	'[Select Тема_Вибір
	Dim List1 As New List(Of String)
	List1.AddRange({"Прут", "Квадрат", "Шестиграник", "Лист", "Лист ромб", "Лист сочевиця", "Лист ПВ", "Настил", "ДСП", "OSB/3", _
					"Дошка", "Брус", "Двотавр", "Кутик", "Труба", "Швелер", "Перо шнека", "Дріт" , "С-подібний профіль"})
	List1.Sort
	If Not String.IsNullOrEmpty(Тема) Then
		i = List1.IndexOf(Тема)
		If i < 0 Then i = 0
	End If
	Тема = InputListBox(oDoc.DisplayName, List1, List1(i), Title := "Тип елемента.", ListName := "Вибіріть заготовку:")
	oRevNumb.Value = Тема']
	
	Dim List2 As New List(Of String)
	Dim j As Integer = 0
	Select Case Тема
	Case "Прут" : Веб_сайт = "ДСТУ 4738"
	Case "Дріт" : Веб_сайт = "ДСТУ 3671-97"
	Case "Квадрат" : Веб_сайт = "ДСТУ 4746"
	Case "Шестиграник" : Веб_сайт = "ДСТУ EN 10061"
	Case "Лист" : Веб_сайт = "ДСТУ 8540"
	Case "Лист ромб", "Лист сочевиця" : Веб_сайт = "ДСТУ 8783"
	Case "Лист ПВ" : Веб_сайт = "ГОСТ 8706-78"
	Case "Настил" : Веб_сайт = "DIN 24537-1"
	Case "ДСП" : Веб_сайт = "ДСТУ ГОСТ 10632"
	Case "OSB/3" : Веб_сайт = "ДСТУ EN 300"
	Case "Дошка", "Брус" : Веб_сайт = "ДСТУ ISO 738"
	Case "Двотавр" : List2.AddRange({"DIN 1025-2", "DIN 1025-4", "DIN 1025-5", "EURONORM 53-62", "ГОСТ 26020-83", "ДСТУ 8768" })
	Case "Кутик" : List2.AddRange({"ДСТУ 2251", "ДСТУ 2254-93", "ДСТУ 2255-93", "ДСТУ 8769", "ДСТУ EN 10056-1" })
	Case "Труба" : List2.AddRange({"ДСТУ 8943", "ДСТУ Б В.2.6-8-95", "ДСТУ 8936", "ДСТУ 8940", "ДСТУ 8938", "ДСТУ 8939", "ДСТУ ISO 1127", _
									"ДСТУ EN 10210-2", "ДСТУ EN 10216-1" })
	Case "Швелер" : List2.AddRange({"DIN 1026-1", "DIN 1026-2", "П ДСТУ 3436-96", "У ДСТУ 3436-96" })
	Case "Перо шнека" :	oRevNumb.Value = "Лист" : Веб_сайт = "ДСТУ 8540" : Call CreatSheetScrew(oDoc)
	Case "С-подібний профіль" : Веб_сайт = "ДСТУ 8808" : Call ProfilThick(oDoc)
	End Select
	
	If Тема = "Двотавр" Or Тема = "Кутик" Or Тема = "Труба" Or Тема = "Швелер" Then
		List2.Sort
		If Not String.IsNullOrEmpty(Веб_сайт) Then
			j = List1.IndexOf(Веб_сайт)
			If j < 0 Then j = 0
		End If
		Веб_сайт = InputListBox("Вибіріть стандарт: " & Тема, List2, List2(j), Title := "Стандарт", ListName := oDoc.DisplayName)
		If Веб_сайт = "П ДСТУ 3436-96" Then
			Веб_сайт = "ДСТУ 3436-96"
			oProject("Stock Number").Value = "П"
		ElseIf Веб_сайт = "У ДСТУ 3436-96" Then
			Веб_сайт = "ДСТУ 3436-96"
			oProject("Stock Number").Value = "У"
		End If
	End If
	
	If Веб_сайт = "Прут" Or Веб_сайт = "Квадрат" Or Веб_сайт = "Шестиграник" Or Тема = "Труба" Then
		If HasSweep(oDef) Then
			Dim oFeat As PartFeature = FindFeatures(oDef)
			If Not IsNothing(oFeat) Then 
				FindSizeProfil(oFeat, Веб_сайт)
			End If
		End If
	End If
	
	oWebLink.Value = Веб_сайт
	
	Try : iLogicVb.RunRule("2_Габарит деталі")
	Catch :	iLogicVb.RunExternalRule("2_DimensionsOfPart")
	End Try
	
	oDoc.Update()
End Sub

Dim oInvApp As Inventor.Application
Dim oMT As MeasureTools
Dim oDoc As PartDocument

Private Function HasSweep(oDef As PartComponentDefinition) As Boolean
	If oDef.Features.Item(1).Type = ObjectTypeEnum.kReferenceFeatureObject Then
		Return True
	Else
		Dim oFeat As PartFeature = oDef.SurfaceBodies.Item(1).CreatedByFeature
		If oFeat.Type = ObjectTypeEnum.kSweepFeatureObject Then
			Dim oSweep As SweepFeature = oDef.SurfaceBodies.Item(1).CreatedByFeature
			Return True
		End If
	End If
	Return False
End Function

Private Function FindFeatures(ByVal oDef As PartComponentDefinition) As PartFeature
	Dim oDriveParts As DerivedPartComponents = oDef.ReferenceComponents.DerivedPartComponents
	If oDriveParts.Count = 0 Then Return Nothing
	Dim oDrivePart As DerivedPartComponent = oDriveParts.Item(1)
	Dim oDerPart As Document = oDrivePart.ReferencedDocumentDescriptor.ReferencedDocument
	Dim oBodyName As String = oDrivePart.SolidBodies.Item(1).Name
	oBodyName = oBodyName.Substring(0, oBodyName.IndexOf("::"))
	Dim oGroundDef As PartComponentDefinition = oDerPart.ComponentDefinition
	For Each oBody As SurfaceBody In oGroundDef.SurfaceBodies
		If oBody.Name = oBodyName Then
			Dim oFeat As PartFeature = oGroundDef.Features(oBody.CreatedByFeature.Name)
			If oFeat.Type = ObjectTypeEnum.kSweepFeatureObject Then
				Return oFeat
			End If
			Exit For
		End If
	Next
	Return Nothing
End Function

Private Function FindSizeProfil(oSweep As SweepFeature, Веб_сайт As String)
	Dim oDef As PartComponentDefinition = oSweep.Parent
	Dim oSketch As PlanarSketch = oSweep.Profile.Parent
	Dim oParams As Parameters = oDef.Parameters
	Dim listParam As New List(Of String)	
	Dim oDimensNameH, oDimensNameW As String
	If oSketch.HasReferenceComponent Then
		Dim oRefDoc As PartDocument = oSketch.ReferenceComponent.ReferencedDocumentDescriptor.ReferencedDocument
		oRefDef = oRefDoc.ComponentDefinition
		oSketch = oRefDef.Sketches(oSketch.Name)
		Dim oDerParam As DerivedParameterTables = oParams.DerivedParameterTables
		Dim oDerParTab As DerivedParameterTable
		Dim oParamsToLink As ObjectCollection = oInvApp.TransientObjects.CreateObjectCollection
		If oSketch.DimensionConstraints.Count = 1 Then
			oDimensNameH = oSketch.DimensionConstraints.Item(1).Parameter.Name
			oParamsToLink.Add(oRefDef.Parameters.Item(oDimensNameH))
		Else
			For Each oDimCon As DimensionConstraint In oSketch.DimensionConstraints
				Dim oParam As Inventor.Parameter
				listParam.Add(oParam.Name & "(" & oParam.Expression & ") = " & oParam.Value * 10 & " " & oParam.Units)
			Next
			If Веб_сайт = "ДСТУ 4738" Or Веб_сайт = "ДСТУ 4746" Or Веб_сайт = "ДСТУ EN 10061" Or Веб_сайт = "ДСТУ 3671-97" Then
				oDimensNameH = InputListBox(oBodyName, listParam, listParam(1), Title := "Параметри:", ListName := "Виберіть січення:")
				oDimensNameH = oDimensNameH.Substring(0, oDimensNameH.IndexOf("("))
			Else
'			Else If Веб_сайт = "ДСТУ 8943" Or Веб_сайт = "ДСТУ Б В.2.6-8-95" Or Веб_сайт = "ДСТУ 8936" Or Веб_сайт = "ДСТУ 8940" Or Веб_сайт = "ДСТУ 8938" _
'				Or Веб_сайт =  "ДСТУ 8939"Or Веб_сайт =  "ДСТУ ISO 1127" Or Веб_сайт = "ДСТУ EN 10210-2" Or Веб_сайт =  "ДСТУ EN 10216-1" Then
				oDimensNameH = InputListBox(oBodyName, listParam, listParam(1), Title := "Параметри:", ListName := "Виберіть висоту:")
				oDimensNameH = oDimensNameH.Substring(0, oDimensNameH.IndexOf("("))
				oDimensNameW = InputListBox(oBodyName, listParam, listParam(1), Title := "Параметри:", ListName := "Виберіть ширину:")
				oDimensNameW = oDimensNameW.Substring(0, oDimensNameW.IndexOf("("))
			End If
			For Each oParam As ModelParameter In oRefDef.Parameters.ModelParameters
				If oParam.Name = oDimensNameH Or oParam.Name = oDimensNameW Then
					oParam.ExposedAsProperty = True						
					Exit For
				End If
			Next
			oParamsToLink.Add(oRefDef.Parameters.Item(oDimensNameH))
			oParamsToLink.Add(oRefDef.Parameters.Item(oDimensNameW))
		End If			
		For Each oDerParTab In oDerParam
			If oDerParTab.ReferencedDocumentDescriptor.ReferencedDocument.fullfilename = oRefDoc.FullFileName Then
				For Each oLinkParam As DerivedParameter In oDerParTab.DerivedParameters
					If oLinkParam.Name = oDimensNameH Then
						GoTo SkipAddLink
					End If
				Next
			End If
		Next
		oDerParTab = oDerParam.Add2(oRefDoc.FullFileName, oParamsToLink)
	Else
		If oSketch.DimensionConstraints.Count = 1 Then
			oDimensNameH = oSketch.DimensionConstraints.Item(1).Parameter.Name
		Else
			Dim ListName As String = "listParameters"
			For Each oDimCon As DimensionConstraint In oSketch.DimensionConstraints
				listParam.Add(oDimCon.Parameter.Name & "(" & oDimCon.Parameter.Expression & ") = " & oDimCon.Parameter.Value * 10 & " " & oDimCon.Parameter.Units)
			Next
			If Веб_сайт = "ДСТУ 4738" Or Веб_сайт = "ДСТУ 4746" Or Веб_сайт = "ДСТУ EN 10061" Or Веб_сайт = "ДСТУ 3671-97" Then
				oDimensNameH = InputListBox(oBodyName, listParam, listParam(1), Title := "Параметри:", ListName := "Виберіть січення:")
				oDimensNameH = oDimensNameH.Substring(0, oDimensNameH.IndexOf("("))
			Else
'			Else If Веб_сайт = "ДСТУ 8943" Or Веб_сайт = "ДСТУ Б В.2.6-8-95" Or Веб_сайт = "ДСТУ 8936" Or Веб_сайт = "ДСТУ 8940" Or Веб_сайт = "ДСТУ 8938" _
'				Or Веб_сайт =  "ДСТУ 8939"Or Веб_сайт =  "ДСТУ ISO 1127" Or Веб_сайт = "ДСТУ EN 10210-2" Or Веб_сайт =  "ДСТУ EN 10216-1" Then
				oDimensNameH = InputListBox(oBodyName, listParam, listParam(1), Title := "Параметри:", ListName := "Виберіть висоту:")
				oDimensNameH = oDimensNameH.Substring(0, oDimensNameH.IndexOf("("))
				oDimensNameW = InputListBox(oBodyName, listParam, listParam(1), Title := "Параметри:", ListName := "Виберіть ширину:")
				oDimensNameW = oDimensNameW.Substring(0, oDimensNameW.IndexOf("("))
			End If
		End If
		Dim oDriveParts As DerivedPartComponents = oDef.ReferenceComponents.DerivedPartComponents
		If oDriveParts.Count >= 1 Then
			Dim oDrivePart As DerivedPartComponent = oDriveParts.Item(1)
			Dim oDerPartDef As DerivedPartDefinition = oDrivePart.Definition
			Dim oDPEnts As DerivedPartEntities = oDerPartDef.Parameters
			Dim oDPEnt As DerivedPartEntity
			For Each oDPEnt In oDPEnts
				If oDPEnt.ReferencedEntity.Name = oDimensNameH Or oDPEnt.ReferencedEntity.Name = oDimensNameW Then
					oDPEnt.IncludeEntity = True
					Exit For
				End If
			Next
			oDrivePart.Definition = oDerPartDef
		End If
	End If
	Dim oUPs As UserParameters = oParams.UserParameters
	Try : oUPs("Висота").Expression = oDimensNameH : Catch 
		oUPs.AddByExpression("Висота", oDimensNameH, kMillimeterLengthUnits) : End Try
	If Not oDimensNameW Is Nothing Then
		Try : oUPs("Ширина").Expression = oDimensNameW : Catch 
			oUPs.AddByExpression("Ширина", oDimensNameW, kMillimeterLengthUnits) : End Try
	Else
		Try : oUPs("Ширина").Expression = oDimensNameH : Catch 
			oUPs.AddByExpression("Ширина", oDimensNameH, kMillimeterLengthUnits) : End Try
	End If	
	SkipAddLink :
End Function

Private Sub ProfilThick(oDoc As PartDocument)
	Dim tName As String
	Dim oDef As PartComponentDefinition = oDoc.ComponentDefinition
	Dim oDriveParts As DerivedPartComponents = oDef.ReferenceComponents.DerivedPartComponents
	Dim oUPs As UserParameters = oDef.Parameters.UserParameters
	If oDriveParts.Count >= 1 Then
		Dim oDrivePart As DerivedPartComponent = oDriveParts.Item(1)
		Dim oDerPartDef As DerivedPartDefinition = oDrivePart.Definition
		Dim oDerPart As Document = oDrivePart.ReferencedDocumentDescriptor.ReferencedDocument
		Dim oBodyName As String = oDrivePart.SolidBodies.Item(1).Name
		oBodyName = oBodyName.Substring(0, oBodyName.IndexOf("::"))
		Dim oGroundDef As PartComponentDefinition = oDerPart.ComponentDefinition
		Dim oFeatName As String
		For Each oBody As SurfaceBody In oGroundDef.SurfaceBodies
			If oBody.Name = oBodyName Then
				oFeatName = oBody.CreatedByFeature.Name
				Exit For
			End If
		Next
		Dim oFeat As PartFeature = oGroundDef.Features(oFeatName)
		If oFeat.Type = kThickenFeatureObject Then '83955200 (Товщина)
			tName = oFeat.Parameters.Item(1).Name
		Else
			tName = CreateListParams(oFeat.Profile.Parent)
		End If
		For Each oDPEnt As DerivedPartEntity In oDerPartDef.Parameters
			If oDPEnt.ReferencedEntity.Name = tName Then
				oDPEnt.IncludeEntity = True
				Exit For
			End If
		Next
		oDrivePart.Definition = oDerPartDef
	Else
		Dim oFeat As PartFeature = oDef.Features(oDef.SurfaceBodies.Item(1).CreatedByFeature.Name)
		tName = CreateListParams(oFeat.Profile.Parent)
	End If
	If String.IsNullOrEmpty(tName) Then Exit Sub
	Try : oUPs("Товщина").Expression = tName : Catch
	oUPs.AddByExpression("Товщина", tName, kMillimeterLengthUnits) : End Try
End Sub

Private Function CreateListParams(ByVal oSketch As PlanarSketch) As String
	Dim tName As String
	Dim ListParam As New ArrayList
	Dim ListName As String = "ListParameters"
	For Each oDimCon As DimensionConstraint In oSketch.DimensionConstraints
		Dim oParam As Inventor.Parameter = oDimCon.Parameter
		ListParam.Add(oParam.Name & "(" & oParam.Expression & ") = " & oParam.Value * 10 & " " & oParam.Units)
	Next
	tName = InputListBox(oBodyName, ListParam, ListName(0), Title := "Параметри.", ListName := "Вибиріть товщину:")
	Return tName.Substring(0, tName.IndexOf("("))
End Function

Private Sub CreatSheetScrew(oDoc As PartDocument)
	Dim oTG As TransientGeometry = oInvApp.TransientGeometry
	Dim oUOM As UnitsOfMeasure = oDoc.UnitsOfMeasure
	Dim oDocDef As PartComponentDefinition = oDoc.ComponentDefinition
	Dim oUserParams As UserParameters = oDocDef.Parameters.UserParameters
	Dim oStates As ModelStates = oDocDef.ModelStates
	oStates.Item(1).Activate()
	oStates.MemberEditScope = MemberEditScopeEnum.kEditAllMembers
	
	Dim oArray, oEdgeLengths, oLengths As New List(Of Double)
	Dim oMin, oMax, L1Size, L2Size, rSize As Double
	
	Dim oBody As SurfaceBody = oDocDef.SurfaceBodies.Item(1)
	
	For Each oFace As Face In oBody.Faces
		oArray.Add(oFace.Evaluator.Area)
	Next
	Dim iFace As Integer = oArray.FindIndex(0, oArray.Count, Function(t) t = oArray.Max) + 1
		
	For Each oEdge As Edge In oBody.Faces.Item(iFace).Edges
		oEdge.Evaluator.GetParamExtents(oMin, oMax)
		oEdge.Evaluator.GetLengthAtParam(oMin, oMax, oLength)
		If Not oEdgeLengths.Contains(Round(oLength, 6)) Then
			oEdgeLengths.Add(Round(oLength, 6))
		Else
			oLengths.Add(Round(oLength, 6))
		End If
	Next
	
	L1Size = oEdgeLengths.Max
	oArray = oEdgeLengths.Distinct().ToList()
	L2Size = oArray.Sum - oLengths.Max - L1Size
	rSize = oLengths.Max * L2Size / (L1Size - L2Size)
	
	Dim L1_name As String = "L1_size_screw"
	Dim L2_name As String = "L2_size_screw"
	Dim r_name As String = "r_size_screw"
		
	Try : oUserParams(L1_name).Value = L1Size
	Catch : oUserParams.AddByValue(L1_name, L1Size, oUOM.LengthUnits) : End Try
	Try : oUserParams(L2_name).Value = L2Size
	Catch : oUserParams.AddByValue(L2_name, L2Size, oUOM.LengthUnits) : End Try
	Try : oUserParams(r_name).Value = rSize
	Catch : oUserParams.AddByValue(r_name, rSize, oUOM.LengthUnits) : End Try
	
	Dim oModName As String = "Розгортка пера шнека"
	
	If IsNothing(oStates(oModName)) Then	
		oLengths.Clear
		
		For Each oEdge As Edge In oBody.Edges
			oEdge.Evaluator.GetParamExtents(oMin, oMax)
			oEdge.Evaluator.GetLengthAtParam(oMin, oMax, oLength)
			oLengths.Add(Round(oLength, 2))
		Next
		
		Dim oSketName As String = "ЕскізПераШнека"
		Dim nameThich As String
		Dim oFeat As PartFeature
		Dim oDriveParts As DerivedPartComponents = oDocDef.ReferenceComponents.DerivedPartComponents
		If oDriveParts.Count >= 1 Then
			Dim oDrivePart As DerivedPartComponent = oDriveParts.Item(1)
			If Not IsNothing(oDrivePart.SolidBodies) Then
				Dim oDerPartDef As DerivedPartDefinition = oDrivePart.Definition
				Dim oDerPart As Document = oDrivePart.ReferencedDocumentDescriptor.ReferencedDocument
				Dim oGroundDef As PartComponentDefinition = oDerPart.ComponentDefinition
				Dim oFeatName As String
				For Each oBodyGround As SurfaceBody In oGroundDef.SurfaceBodies
					If oBodyGround.Name = oBody.Name Then
						oFeatName = oBodyGround.CreatedByFeature.Name
						Exit For
					End If
				Next
				oFeat = oGroundDef.Features(oFeatName)
				If oFeat.Type = kThickenFeatureObject Then '83955200 (Товщина)
					nameThich = oFeat.Parameters.Item(1).Name
				Else
					If oLengths.Min() = Round(oFeat.Parameters.Item(1).Value , 5) Then
						nameThich = oFeat.Parameters.Item(1).Name
					Else
						Dim oSketch As PlanarSketch = oFeat.Profile.Parent
						For Each oDimCon As DimensionConstraint In oSketch.DimensionConstraints
							If oLengths.Min() = Round(oDimCon.Parameter.Value, 5) Then
								nameThich = oDimCon.Parameter.Name
								Exit For
							End If
						Next
					End If
				End If	
				For Each oDPEnt As DerivedPartEntity In oDerPartDef.Parameters
					If oDPEnt.ReferencedEntity.Name = nameThich Then
						oDPEnt.IncludeEntity = True
						Exit For
					End If
				Next
				oDrivePart.Definition = oDerPartDef
			ElseIf Not IsNothing(oDrivePart.SurfaceBodies) Then
				oFeat = oDocDef.Features(oBody.CreatedByFeature.Name)
				If oFeat.Type = kThickenFeatureObject Then
					nameThich = oFeat.Parameters.Item(1).Name
				Else
					For Each oUseParam As UserParameter In oUserParams
						If oLengths.Min() = Round(oUseParam.Value, 5) Then
							nameThich = oUseParam.Name
							Exit For
						End If
					Next
				End If
			End If
		Else
			oFeat = oDocDef.Features(oBody.CreatedByFeature.Name)
			If oFeat.Type = kThickenFeatureObject Then
				nameThich = oFeat.Parameters.Item(1).Name
			Else
				For Each oUseParam As UserParameter In oUserParams
					If oLengths.Min() = Round(oUseParam.Value, 5) Then
						nameThich = oUseParam.Name
						Exit For
					End If
				Next
			End If
		End If
		
		oStates.Add(oModName)
		oStates.MemberEditScope = MemberEditScopeEnum.kEditActiveMember
		oDocDef.Features(oBody.CreatedByFeature.Name).Suppressed = True
		
		Dim oSkets As PlanarSketches = oDocDef.Sketches
		
		Dim oSket As PlanarSketch	
		oSket = oSkets.Add(oDocDef.WorkPlanes.Item(3))
		oSket.Name = oSketName
		
		Dim oDot As SketchEntity
		oDot = oSket.AddByProjectingEntity(oDocDef.WorkPoints.Item(1))
		oAxe = oSket.AddByProjectingEntity(oDocDef.WorkPlanes.Item(1))
		oAxe.Construction = True
		
		Dim oArc1 As SketchArc
		oArc1 = oSket.SketchArcs.AddByCenterStartEndPoint(oDot, oTG.CreatePoint2d(-5, 0), oTG.CreatePoint2d(5, 0), True)
		oSket.GeometricConstraints.AddCoincident(oDot, oArc1.CenterSketchPoint)
		
		Dim oArc2 As SketchArc
		oArc2 = oSket.SketchArcs.AddByCenterStartEndPoint(oDot, oTG.CreatePoint2d(-10, 0), oTG.CreatePoint2d(10, 0), True)
		oSket.GeometricConstraints.AddCoincident(oArc1.CenterSketchPoint, oArc2.CenterSketchPoint)
		
		Dim oLine1 As SketchLine
		oLine1 = oSket.SketchLines.AddByTwoPoints(oArc2.StartSketchPoint, oArc1.StartSketchPoint)
		oSket.GeometricConstraints.AddCoincident(oDot, oLine1)
		
		Dim oLine2 As SketchLine
		oLine2 = oSket.SketchLines.AddByTwoPoints(oArc1.EndSketchPoint, oArc2.EndSketchPoint)
		oSket.GeometricConstraints.AddCoincident(oDot, oLine2)
		oSket.GeometricConstraints.AddSymmetry(oLine1, oLine2, oAxe)
		
		Dim Arc2Lang = oSket.DimensionConstraints.AddArcLength(oArc2, oTG.CreatePoint2d(0, -15), False)
		Dim Arc1Lang = oSket.DimensionConstraints.AddArcLength(oArc1, oTG.CreatePoint2d(0, -12), False)
		Dim Arc1Rad = oSket.DimensionConstraints.AddRadius(oArc1, oTG.CreatePoint2d(0, -6), False)
		Arc2Lang.Parameter.Expression = L1_name
		Arc1Lang.Parameter.Expression = L2_name
		Arc1Rad.Parameter.Expression = r_name
			
		Dim oProfile As Profile
		oProfile = oSket.Profiles.AddForSolid
		
		Dim oExtrudeDef As ExtrudeDefinition
		oExtrudeDef = oDocDef.Features.ExtrudeFeatures.CreateExtrudeDefinition(oProfile, PartFeatureOperationEnum.kNewBodyOperation)
		
		If nameThich Is Nothing Then nameThich = oUOM.ConvertUnits(oLengths.Min(), UnitsTypeEnum.kCentimeterLengthUnits, oUOM.LengthUnits)
		oExtrudeDef.SetDistanceExtent(nameThich, PartFeatureExtentDirectionEnum.kSymmetricExtentDirection)
		
		Dim oExtrude As ExtrudeFeature
		oExtrude = oDocDef.Features.ExtrudeFeatures.Add(oExtrudeDef)
		oExtrude.Name = "ВидавленняПераШнека"
		
		oStates.MemberEditScope = MemberEditScopeEnum.kEditAllMembers
		oStates.Item(1).Activate()
	End If

End Sub
