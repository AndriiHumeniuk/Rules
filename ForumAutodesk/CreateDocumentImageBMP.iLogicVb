AddReference "System.Drawing"
AddReference "stdole"
AddReference "System.Windows.Forms"
Class ThisRule
	Sub Main
		Break
		Dim oDoc As Document = ThisDoc.Document
		Dim oThumb As stdole.IPictureDisp
		Do
			oThumb = oDoc.Thumbnail
		Loop While oThumb.Handle < 0
		Dim oAHConverter As New AxHostConverter
		Dim oImage As System.Drawing.Image = oAHConverter.GetImageFromIPictureDisp(oThumb)
		'this call must be created, but is never used
		Dim myCallback As New System.Drawing.Image.GetThumbnailImageAbort(AddressOf ThumbnailCallback)
		'create a thumbnail before save - seems to generate a better quality
		oImage.GetThumbnailImage(180, 180, myCallback, IntPtr.Zero).Save("C:\Temp\Thumbnail To BMP test.bmp", System.Drawing.Imaging.ImageFormat.Bmp)
	End Sub

	Public Function ThumbnailCallback() As Boolean
		Return False
	End Function
End Class

Class AxHostConverter
	Inherits System.Windows.Forms.AxHost
	Public Sub New()
		'MyBase.New("{63109182-966B-4e3c-A8B2-8BC4A88D221C}")
		MyBase.New((New Guid).ToString)
	End Sub
	Public Function GetImageFromIPictureDisp(ByVal IPDisp As stdole.IPictureDisp) As System.Drawing.Image
		Return MyBase.GetPictureFromIPicture(IPDisp)
	End Function
End Class
