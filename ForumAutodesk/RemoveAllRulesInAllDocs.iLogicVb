Sub Main
	Dim oInvApp As Inventor.Application = ThisApplication
	Dim oDoc As Document = oInvApp.ActiveDocument
	Dim oAuto As IiLogicAutomation = iLogicVb.Automation
	If Not TypeOf oDoc Is AssemblyDocument Then Exit Sub
	Dim oAsmDoc As AssemblyDocument = oDoc
	oAuto.DeleteAllRules(oAsmDoc)
	Dim oRefDocs As DocumentsEnumerator = oAsmDoc.AllReferencedDocuments
	Dim oOccs As ComponentOccurrences = oAsmDoc.ComponentDefinition.Occurrences
	Dim oPBar As Inventor.ProgressBar
	oPBar = oInvApp.CreateProgressBar(False, oRefDocs.Count, "Copy ryles...")
	Dim i As Integer = 1
	oPBar.Message = "Loading..."
	Dim oTM As Transaction 
	oTM = oInvApp.TransactionManager.StartTransaction(oAsmDoc, "RemoveRulesInAllDocs")
	For Each oRefDoc As Document In oRefDocs
		oPBar.Message = "Remove rules in docs. Progress " & i & " of " & oRefDocs.Count & "."
		If oOccs.AllReferencedOccurrences(oRefDoc).Count > 0 Then
			If Not oRefDoc.IsModifiable Then Continue For
			oAuto.DeleteAllRules(oRefDoc)
			oRefDoc.Save()
		End If
		oPBar.UpdateProgress
		i += 1
	Next
	oPBar.Close()
	oTM.End()
End Sub
