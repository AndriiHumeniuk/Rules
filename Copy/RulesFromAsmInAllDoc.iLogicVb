Sub Main
	Dim oDoc As Document = ThisDoc.Document
	If Not TypeOf oDoc Is AssemblyDocument Then Exit Sub
	Dim oDocFrom As AssemblyDocument = oDoc
	Dim oOccs As ComponentOccurrences = oDocFrom.ComponentDefinition.Occurrences
	Dim oPBar As Inventor.ProgressBar = ThisApplication.CreateProgressBar(False, oDocFrom.AllReferencedDocuments.Count, "Copy ryles...")
	Dim i As Integer = 1
	oPBar.Message = "Loading..."
	Dim oTM As Transaction = ThisApplication.TransactionManager.StartTransaction(oDocFrom, "CopyRulesInOccs")
	For Each copyTo As Document In oDocFrom.AllReferencedDocuments
		oPBar.Message = "Copy ryles in document. Progress " & i & " of " & oDocFrom.AllReferencedDocuments.Count & "."
		If oOccs.AllReferencedOccurrences(copyTo).Count > 0 Then
			If copyTo.IsModifiable Then
				Call CopyRules(oDocFrom, copyTo)
				Call CopyEventsPropSet(oDocFrom, copyTo)
			End If
		End If
		oPBar.UpdateProgress
		i += 1
	Next
	oPBar.Close()
	oTM.End()
End Sub

Sub CopyRules(CopyFrom As Document, CopyTo As Document)
	For Each oRule As iLogicRule In iLogicVb.Automation.Rules(CopyFrom)
		Dim oCopy As iLogicRule
		Try
			oCopy = iLogicVb.Automation.GetRule(CopyTo, oRule.Name)
			oCopy.Text = oRule.Text
		Catch
			oCopy = iLogicVb.Automation.AddRule(CopyTo, oRule.Name, oRule.Text)
		End Try
	Next
End Sub

Sub CopyEventsPropSet(CopyFrom As Document, CopyTo As Document)
	Dim oPropSet As Inventor.PropertySet = CopyFrom.PropertySets("{2C540830-0723-455E-A8E2-891722EB4C3E}")
	Try : CopyTo.PropertySets("{2C540830-0723-455E-A8E2-891722EB4C3E}").Delete() : Catch : End Try
	Dim newPropSet As Inventor.PropertySet = CopyTo.PropertySets.Add("_iLogicEventsRules", "{2C540830-0723-455E-A8E2-891722EB4C3E}")
	For Each prop As Inventor.Property In oPropSet
		newPropSet.Add(prop.Value, prop.Name, prop.PropId)
	Next
End Sub
