Sub main
	Dim oInvApp As Inventor.Application = ThisApplication
	Dim oDraw As DrawingDocument = TryCast(oInvApp.ActiveDocument, DrawingDocument)
	If oDraw Is Nothing Then Exit Sub
	Dim oTM As TransactionManager = oInvApp.TransactionManager	
	Dim oSheets As Sheets = oDraw.Sheets
	Dim oFirstView As DrawingView = GetFirstView(oSheets)
	
	If oFirstView Is Nothing Then Exit Sub
		
	Dim ViewLetter As Char() = {"A","B","C","D","E","F","G","H","J","K","L","M","N","P","R","S","T","U","V","W","X","Y"}
	Dim iViewCount As Integer = 0
	
	Dim o1stViewScale As String = oFirstView.ScaleString
    Dim oView_Number As String = "<StyleOverride Underline='False'><DrawingViewName/></StyleOverride>"
	Dim oView_Scale As String = "<StyleOverride Underline='False'> (<DrawingViewScale/></StyleOverride>)"
	Dim oView_Name As String
	
	Dim numbList As New ArrayList	
			
	Dim newTM As Transaction = oTM.StartTransaction(oDraw, "ChangeViewsName")
	
	For i As Integer = 1 To oSheets.Count
		numbList.Add(oSheets(i).Name)
	Next
	
	For Each oSheet As Sheet In oSheets
	    For Each oView As DrawingView In oSheet.DrawingViews
			If Not oView.ShowLabel Then Continue For
			Dim sNameView As String = oView.Label.FormattedText
			If o1stViewScale = oView.ScaleString Then
				oView_Name = oView_Number
			Else
				oView_Name = oView_Number & oView_Scale
			End If
				
			If Not IsNothing(oView.ParentView) Then
				If oView.ViewType = DrawingViewTypeEnum.kAssociativeDraftDrawingViewType Then Continue For
'				If oView.ViewType = DrawingViewTypeEnum.kAuxiliaryDrawingViewType Then Continue For
				If oView.ViewType = DrawingViewTypeEnum.kCustomDrawingViewType Then Continue For
				If oView.ViewType = DrawingViewTypeEnum.kDefaultDrawingViewType Then Continue For
'				If oView.ViewType = DrawingViewTypeEnum.kDetailDrawingViewType Then Continue For
				If oView.ViewType = DrawingViewTypeEnum.kDraftDrawingViewType Then Continue For
				If oView.ViewType = DrawingViewTypeEnum.kOLEAttachmentDrawingViewType Then Continue For
				If oView.ViewType = DrawingViewTypeEnum.kOverlayDrawingViewType Then Continue For
'				If oView.ViewType = DrawingViewTypeEnum.kProjectedDrawingViewType Then Continue For
'				If oView.ViewType = DrawingViewTypeEnum.kSectionDrawingViewType Then Continue For
				If oView.ViewType = DrawingViewTypeEnum.kStandardDrawingViewType Then Continue For
					
				If iViewCount < ViewLetter.Length Then
					oView.Name = ViewLetter(iViewCount)
				Else
					Dim dMaxCount As Integer = ViewLetter.Length + ViewLetter.Length				
					If ViewLetter.Length <= iViewCount And iViewCount < (dMaxCount) Then
						oView.Name = ViewLetter(0) & ViewLetter(iViewCount - ViewLetter.Length)
					Else
						Dim iStepNumb As Double = iViewCount - (dMaxCount - 1)
						Dim iStep As Integer = Ceil(iStepNumb / ViewLetter.Length)
						Dim iNumb As Double = iViewCount - (ViewLetter.Length * (iStep+1))
						oView.Name = ViewLetter(iStep) & ViewLetter(iNumb)
					End If
				End If
		    	iViewCount = iViewCount + 1
				Dim sSheetName As String = oView.ParentView.Parent.Name
				If oView.ViewType = DrawingViewTypeEnum.kSectionDrawingViewType _
					And oView.Label.Text.Contains("-") Then
					sNameView = oView_Number & "-" & oView_Name
				Else
					sNameView = oView_Name
				End If	
				If sSheetName <> oView.Parent.Name Then
					sNameView = sNameView & " (" & numbList.IndexOf(sSheetName) + 1 & ")"
				End If				
			Else
				sNameView = oView_Name
			End If
			If oView.Rotation = 0 Then
				oView.Label.FormattedText = sNameView
			Else
				sNameView = CheckRotateView(oView)
				If sNameView Is Nothing Then Continue For
				Try : oView.Label.FormattedText = sNameView
				Catch : End Try
			End If
	    Next
	Next
	
	newTM.End()
	
End Sub

Private Function GetFirstView(ByVal oSheets As Sheets) As DrawingView
	For iSheet As Integer = 1 To oSheets.Count
		If oSheets(iSheet).DrawingViews.Count = 0 Then Continue For
		Return oSheets(iSheet).DrawingViews(1)
	Next
	Return Nothing
End Function

Private Function CheckRotateView(ByVal oView As DrawingView) As String
	Dim dDeg As Double = Round(oView.Rotation * 180 / PI, 2)
	Do While dDeg > 360.01
		dDeg = dDeg - 360
	Loop
	If dDeg <> 0 And dDeg <> 360 Then
		Dim sDeg, sRotate As String
		If Abs(dDeg) < 180.01 Then
			sDeg = Abs(dDeg) & ChrW(176)
			If dDeg < 0 Then : sRotate = ChrW(&H21B7)
			Else : sRotate = ChrW(&H21B6)
			End If
		Else
			sDeg = Abs(dDeg) - 180 & ChrW(176)
			If dDeg < 0 Then : sRotate = ChrW(&H21B6)
			Else : sRotate = ChrW(&H21B7)
			End If
		End If
    	Return oView.Label.FormattedText & " <StyleOverride Font='@Arial Unicode MS' FontSize='0,8'>" _
				& sRotate & " </StyleOverride>" & sDeg
	End If
	Return Nothing
End Function
