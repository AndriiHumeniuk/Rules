' <FireOthersImmediately>False</FireOthersImmediately>
Sub main()
	If TypeOf ThisDoc.Document Is DrawingDocument Then		
		Dim oDoc As DrawingDocument = ThisDoc.Document
		Dim oCompDoc As Document = ThisApplication.Documents.Open(oDoc.ReferencedDocumentDescriptors.Item(1).FullDocumentName, False)
		Dim Colors As Object
		Item = 0
		Colors = CreateObject("Scripting.Dictionary")
				
		If TypeOf oCompDoc Is AssemblyDocument Then
			Dim doc As AssemblyDocument = oCompDoc
			Dim oAssyDef As AssemblyComponentDefinition = doc.ComponentDefinition
			Dim oBOM As BOM = oAssyDef.BOM
			oBOM.PartsOnlyViewEnabled = True
			Dim oBOMViewPO As BOMView = oBOM.BOMViews.Item("Только детали")
			Call FindParts(oBOMViewPO, Colors)
		ElseIf TypeOf oCompDoc Is PartDocument Then
			Dim oDef As PartComponentDefinition = oCompDoc.ComponentDefinition
			Call ReadPart(oDef, Colors)
		Else
			MessageBox.Show("Данне правило призначення для роботи з кресленнями збірок або деталей.", "Пимилка!")
			Exit Sub
		End If
'[		Writing colors in properties of drawing
		Dim i As Integer = 1
		Dim oProgressBar As Inventor.ProgressBar
		Dim oCustomPropertySet As PropertySet
		oCustomPropertySet = oDoc.PropertySets.Item("Inventor User Defined properties")
		oMessage = "Updating... " 
		oProgressBar = ThisApplication.CreateProgressBar(False, oCustomPropertySet.Count, oMessage)
	    oProgressBar.Message = ("Creating new custom properties... ")
		For Each oOldColor In oCustomPropertySet
			If oOldColor.Name.Contains("Color") Then
				oOldColor.Delete()
			End If
		Next
		Dim iColor As Long = 1
		For Each Item In Colors
			On Error Resume Next
			oCustomPropertySet.Add(Item, "Color" & iColor & " Name")
			oCustomPropertySet.Add(Round(Colors(Item), 3) & " м²", "Color" & iColor & " Value")
			If Item.Contains("RAL") Then
				Dim assetLib As AssetLibrary = ThisApplication.AssetLibraries.Item("5F1643F1-74AC-4477-A0D1-3F4A78F70BE8")
				Dim asset As Asset = Nothing
				asset = assetLib.AppearanceAssets.Item(Item)
				Dim generic_color As ColorAssetValue
				generic_color = asset.Item(13)
				oCustomPropertySet.Add("RGB(" & generic_color.Value.Red & "," & generic_color.Value.Green & _
					"," & generic_color.Value.Blue & ")", "Color" & iColor & " RGB")
			End If
			iColor = iColor+1
		Next']
		oProgressBar.UpdateProgress
		oProgressBar.Close
	Else
		MessageBox.Show("Данне правило призначення для роботи з кресленнями", "Пимилка!")
		Exit Sub
	End If
End Sub

Public Sub FindParts(oBOMViewPO As BOMView, Colors As Object)

	Dim i As Integer = 1
	Dim oProgressBar As Inventor.ProgressBar
    oMessage = "Updating... " 
	oProgressBar = ThisApplication.CreateProgressBar(False, oBOMViewPO.BOMRows.Count, oMessage)
    oProgressBar.Message = ("Loading... ")
	
	For Each oBOMRowPO As BOMRow In oBOMViewPO.BOMRows
	    Dim oCompDef As ComponentDefinition = oBOMRowPO.ComponentDefinitions.Item(1)
		If oCompDef.Type = kPartComponentDefinitionObject Then
			If oCompDef.BOMStructure = BOMStructureEnum.kNormalBOMStructure Or
				oCompDef.BOMStructure = BOMStructureEnum.kPurchasedBOMStructure Then
				Dim strLocName, strLocType As String
				Dim oPartDoc As PartDocument = oCompDef.Document
				oPartDoc.GetLocationFoundIn(strLocName, strLocType)
				If Not strLocType = kLibraryLocation Then
					Dim Qty As Integer = oBOMRowPO.ItemQuantity
					Call ReadPart(oCompDef, Colors, Qty)
				End If
			End If
		End If
        oProgressBar.Message = ("Calculating area of colors. Progress " & i & " of " & oBOMViewPO.BOMRows.Count & ".")
        oProgressBar.UpdateProgress
		i = i+1
	Next
	oProgressBar.Close
End Sub

Public Sub ReadPart(oOccDef As ComponentDefinition, Colors As Object)
	oFaces = oOccDef.SurfaceBodies(1).Faces
	For Each oFace In oFaces
	    Colors(oFace.Appearance.DisplayName) = Colors(oFace.Appearance.DisplayName) + oFace.Evaluator.Area / 10000
	Next
End Sub

Public Sub ReadPart(oOccDef As ComponentDefinition, Colors As Object, Qty As Integer)
	oFaces = oOccDef.SurfaceBodies(1).Faces
	For Each oFace In oFaces
	    Colors(oFace.Appearance.DisplayName) = Colors(oFace.Appearance.DisplayName) + (oFace.Evaluator.Area * Qty) / 10000
	Next
End Sub
