Sub main
	Dim oApp As Inventor.Application = ThisApplication
	Dim oDoc As Document = oApp.ActiveDocument
	If TypeOf oDoc Is AssemblyDocument Then
		Dim oADoc As AssemblyDocument = oDoc
		Dim oDict As New Dictionary(Of String, Integer)
		Dim oProgBar As Inventor.ProgressBar
		Dim iRefDoc As Integer = 1
		oProgBar = oApp.CreateProgressBar(False, oADoc.AllReferencedDocuments.Count, "Count parameters...")
		For Each oRefDoc As Document In oADoc.AllReferencedDocuments
			oProgBar.Message = "Count parameters of component. Progress " & iRefDoc & " of " & oADoc.AllReferencedDocuments.Count & "."
			oProgBar.UpdateProgress
			If Not oRefDoc.IsModifiable Then Continue For
			Call CountParamsInDoc(oRefDoc.ComponentDefinition, oDict)
			iRefDoc += 1
		Next
		oProgBar.Close()
		If oDict.Count = 0 Then Exit Sub
		Dim iParams As New List(Of Integer)
		iParams.AddRange(oDict.Values)
		Dim iSum As Integer = iParams.Sum()
		Dim dPersent As Double
		iParams.Sort()
		Dim sFullUserText As String
		For iP As Integer = iParams.Count - 1 To 0 Step -1
			For i As Integer = oDict.Count - 1 To 0 Step -1
				If iParams(iP) = oDict.Values(i) Then
					dPersent = (oDict.Values(i) / iSum) * 100
					sFullUserText += oDict.Keys(i) & ": параметрів - " & oDict.Values(i) & " (" & Round(dPersent, 3) & "%)" & vbNewLine
				End If
			Next i
		Next iP
		If Not String.IsNullOrEmpty(sFullUserText) Then MessageBox.Show(sFullUserText, "Загальна кільк. парам.: " & iSum)
	End If
End Sub

Private Function CountParamsInDoc(ByVal oDef As ComponentDefinition, ByRef oDict As Dictionary(Of String, Integer))
	Dim sName As String = oDef.Document.PropertySets("Inventor Summary Information")("Author").Value
	Dim oModParams As ModelParameters = oDef.Parameters.ModelParameters
	If String.IsNullOrEmpty(sName) Or oModParams.Count = 0 Then Exit Function
	If oDict.ContainsKey(sName) Then
		oDict(sName) = oDict(sName) + oModParams.Count
	Else
		oDict.Add(sName, oModParams.Count)
	End If
End Function
